# RequirementsComplianceMatrix_TeamElectRAM

## #1: Estimated Perlinimary Design Time (Functional)
The Aircraft must go into service in 2035 with systems varified by 2034.

### #2: Preliminary Design Timeline (Functional)
Estimated time to construct and integrate all parts into working aircraft.

#### #13: Structures Design (Functional)
The perliminary geometry of the aircraft and materials used, including estimated timeline and costs.

##### #14: Storage (Functional)
It is required that the aircraft is designed to support each passenger bringing a personal bag and a checked bag.

##### #15: Comfort (Functional)
Interior designed to optimize passenger comfort with overhead storage and the main walkway being stand-up height.

##### #16: Passenger Capacity (Functional)
The Aircraft must seat at least 9 passengers.

#### #19: Propultion System (Functional)
System through which aircraft generates thrust

##### #38: Engine Power (Functional)
The aircraft’s engine take-off power must be less than 1200 horsepower.

##### #39: Engine Design (Functional)
It is required that the aircraft rely on single or multi-engine configuration.

#### #28: Stability and Control System (Functional)
System to balance aerodynamic forces and pilot inputs to maintain safe controllable flight

##### #29: VFR and IFR flight with autopilot (Functional)
The pilot must be able to fly with VFR (Visual Flight Rules) where the pilot can fly from visual navigation and IFR (Instrument Flight Rules) where the pilot can fly relying on instrument navigaton with a systems autopilot.

##### #47: Cockpit Flight Data and Voice Recorders (Functional)
Aircraft must be equipped with flight data recorders and cockpit voice recorders.

##### #48: Controlability (Functional)
The aircraft must be controllable and maneuverable without requiring exceptional piloting skills.

### #5: Estimated Perliminary Systems Timeline (Functional)
Estimated time to test and verify Aircraft Systems.

## #10: Operating Costs (Functional)
To be profitable in RAM market it is required that the aircraft have lower direct operating costs when comparable aircraft.

## #21: Saftey (Functional)
Aircraft must meet requirements:
- Be compliant with FAR Code of Regulations Part 36.301.
- Meet FAA Regulations for Certification.
- Must be compliant flying in controlled and uncontrolled airspace

### #24: Part 36.301 (Functional)
Aircraft must be compliant with FAR Code of Regulations Part 36.301

### #26: FAA Regulations (Functional)
Aircraft must meet FAA Regulations for Certification

### #27: Controlled/Uncontrolled Airspace (Functional)
Aircraft must be compliant flying in controlled and uncontrolled airspace

### #32: Emergency Maneuvers (Functional)
Capable of facilitating rapid and safe evacuations in the conditions following an emergency landing.

## #22: Wingspan (Functional)
Aircraft must have a wingspan that categorizes the aircraft under ICAO Code C (≤ 36 feet).

## #40: Performance (Functional)
Performance of different aspcet for the aircraft to meet mission requirements

### #41: Takeoff Distance (Functional)
The aircraft must be able to takeoff and land within a distance of no greater than 4000 feet.

### #42: Range (Functional)
The aircraft must have a range of over 300 nautical miles.

### #43: Icing (Functional)
The aircraft must be capable of flight in known icing conditions.

### #44: Speed (Functional)
The aircraft shall be capable of traveling at speeds faster than 130 knots.

### #45: Max Takeoff Weight (Functional)
The aircraft should weigh no more than 19,500 pounds at the maximum takeoff weight.

### #49: Flight Manual (Functional)
An airplane flight manual must be provided containing applicable performance information.
